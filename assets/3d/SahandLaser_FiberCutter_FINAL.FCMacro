# -*- coding: utf-8 -*-
# ==========================================================
# SAHAND LASER - Fiber Laser Cutter FINAL Visual CAD Model
# FreeCAD Macro
# Approximate overall dimensions: 4000 x 2000 x 700 mm
# Nominal cutting area: 3000 x 1500 mm
#
# IMPORTANT:
# This is the FINAL VISUAL / WEBSITE-READY MASTER MODEL based
# on the current reference photos and approximate dimensions.
# It is NOT a manufacturing-certified mechanical drawing.
# ==========================================================

import FreeCAD as App
import Part

try:
    import FreeCADGui as Gui
except Exception:
    Gui = None

DOC_NAME = "SahandLaser_FiberCutter_FINAL"

# ---------- reset ----------
for d in list(App.listDocuments().values()):
    if d.Name == DOC_NAME:
        App.closeDocument(d.Name)
doc = App.newDocument(DOC_NAME)

# ---------- PARAMETERS ----------
L = 4000.0
W = 2000.0
BODY_H = 700.0
WORK_L = 3000.0
WORK_W = 1500.0

FRAME_Z = 150.0
BED_X = (L-WORK_L)/2
BED_Y = (W-WORK_W)/2
BED_Z = 440.0

YRAIL_Z = 610.0
GANTRY_X = 2100.0
GANTRY_Z = 735.0
GANTRY_W = 245.0
GANTRY_H = 250.0

# ---------- COLORS ----------
BLUE       = (0.055, 0.255, 0.455)
BLUE_LIGHT = (0.085, 0.355, 0.610)
BLUE_DARK  = (0.035, 0.120, 0.215)
BLACK      = (0.045, 0.045, 0.055)
DARKGRAY   = (0.18, 0.19, 0.21)
MIDGRAY    = (0.42, 0.44, 0.47)
STEEL      = (0.72, 0.74, 0.77)
SILVER     = (0.84, 0.86, 0.89)
GREEN      = (0.06, 0.92, 0.28)
RED        = (0.90, 0.04, 0.05)
WHITE      = (0.92, 0.93, 0.94)
YELLOW     = (0.95, 0.68, 0.08)

# ---------- helpers ----------
def grp(name, label):
    g = doc.addObject("App::DocumentObjectGroup", name)
    g.Label = label
    return g

def feat(name, shape, color=BLUE, label=None):
    o = doc.addObject("Part::Feature", name)
    o.Shape = shape
    if label: o.Label = label
    try:
        o.ViewObject.ShapeColor = color
        o.ViewObject.LineColor = (0.12,0.12,0.12)
        o.ViewObject.LineWidth = 1.0
    except:
        pass
    return o

def box(name,x,y,z,dx,dy,dz,color=BLUE,label=None):
    return feat(name,Part.makeBox(dx,dy,dz,App.Vector(x,y,z)),color,label)

def cz(name,x,y,z,r,h,color=STEEL,label=None):
    return feat(name,Part.makeCylinder(r,h,App.Vector(x,y,z),App.Vector(0,0,1)),color,label)

def cx(name,x,y,z,r,h,color=STEEL,label=None):
    return feat(name,Part.makeCylinder(r,h,App.Vector(x,y,z),App.Vector(1,0,0)),color,label)

def cy(name,x,y,z,r,h,color=STEEL,label=None):
    return feat(name,Part.makeCylinder(r,h,App.Vector(x,y,z),App.Vector(0,1,0)),color,label)

def add(g, *objs):
    for o in objs:
        if o: g.addObject(o)

def chamfered_box(name,x,y,z,dx,dy,dz,ch=30,color=BLUE,label=None):
    s = Part.makeBox(dx,dy,dz,App.Vector(x,y,z))
    try:
        edges = [e for e in s.Edges if abs((e.Vertexes[-1].Point-e.Vertexes[0].Point).z) > dz*0.8]
        if edges:
            s = s.makeChamfer(ch, edges[:min(4,len(edges))])
    except:
        pass
    return feat(name,s,color,label)

# ---------- groups ----------
G_PARAM = grp("G00_PARAMETERS","00 - Parameters")
G_FRAME = grp("G01_FRAME","01 - Main chassis")
G_BED = grp("G02_BED","02 - Cutting bed")
G_MOTION = grp("G03_MOTION","03 - Rails / rack / gantry")
G_CARR = grp("G04_CARRIAGE","04 - Z carriage / laser head")
G_COV = grp("G05_COVERS","05 - Covers / body panels")
G_CHAIN = grp("G06_CABLE_CHAINS","06 - Cable chains")
G_CTRL = grp("G07_CONTROL","07 - Control console")
G_DETAIL = grp("G08_DETAILS","08 - Bolts / vents / wiring / details")

# ---------- spreadsheet ----------
sh = doc.addObject("Spreadsheet::Sheet","Parameters")
sh.Label = "Reference dimensions"
rows = [
("A1","Parameter"),("B1","Value_mm"),
("A2","Overall length"),("B2",str(L)),
("A3","Overall width"),("B3",str(W)),
("A4","Body height"),("B4",str(BODY_H)),
("A5","Cutting length"),("B5",str(WORK_L)),
("A6","Cutting width"),("B6",str(WORK_W)),
("A7","Status"),("B7","FINAL visual master"),
("A8","Note"),("B8","Approximate model from photos - not production certified"),
]
for c,v in rows: sh.set(c,v)
G_PARAM.addObject(sh)

# ==========================================================
# 01 MAIN CHASSIS
# ==========================================================
add(G_FRAME,
    box("BaseSkid_L",60,85,0,L-120,85,70,BLACK,"Left base skid"),
    box("BaseSkid_R",60,W-170,0,L-120,85,70,BLACK,"Right base skid")
)

for xx in (160,900,1700,2500,3300,3760):
    for yy in (130,W-210):
        add(G_FRAME,
            box(f"FootPad_{xx}_{yy}",xx,yy,0,105,105,25,BLACK,"Foot pad"),
            cz(f"FootStem_{xx}_{yy}",xx+52,yy+52,25,25,92,SILVER,"Adjustable foot"),
            cz(f"FootNut_{xx}_{yy}",xx+52,yy+52,105,34,18,STEEL,"Foot lock nut")
        )

add(G_FRAME,
    box("MainBeam_L",125,180,FRAME_Z,L-250,145,190,BLUE_DARK,"Left main beam"),
    box("MainBeam_R",125,W-325,FRAME_Z,L-250,145,190,BLUE_DARK,"Right main beam")
)

for i,xx in enumerate((250,720,1190,1660,2130,2600,3070,3540)):
    add(G_FRAME, box(f"CrossMember_{i+1}",xx,315,FRAME_Z+20,105,W-630,145,BLUE_DARK,"Main cross member"))

for yy in (455,730,1005,1280,1555):
    add(G_FRAME, box(f"LongInner_{yy}",340,yy,330,L-680,68,85,DARKGRAY,"Internal longitudinal support"))

# ==========================================================
# 02 CUTTING BED
# ==========================================================
add(G_BED,
    box("BedOuterFrame",BED_X,BED_Y,BED_Z,WORK_L,WORK_W,70,BLUE_DARK,"Cutting bed frame"),
    box("BedFrontRail",BED_X,BED_Y,BED_Z+70,WORK_L,55,55,MIDGRAY,"Bed front rail"),
    box("BedRearRail",BED_X,BED_Y+WORK_W-55,BED_Z+70,WORK_L,55,55,MIDGRAY,"Bed rear rail")
)

for yy in (BED_Y+145,BED_Y+430,BED_Y+715,BED_Y+1000,BED_Y+1285):
    add(G_BED,box(f"SlatCarrier_{int(yy)}",BED_X+35,yy,BED_Z+70,WORK_L-70,55,35,MIDGRAY,"Slat carrier"))

for i in range(64):
    xx=BED_X+45+i*((WORK_L-90)/63)
    add(G_BED,box(f"CuttingSlat_{i+1:02d}",xx,BED_Y+40,BED_Z+105,10,WORK_W-80,120,BLACK,"Cutting slat"))

# ==========================================================
# 03 MOTION / RAILS / GANTRY
# ==========================================================
for side,yy in (("L",145),("R",W-235)):
    add(G_MOTION,
        box(f"YSupport_{side}",200,yy,555,L-400,90,62,BLUE,"Y rail support"),
        box(f"YRail_{side}",245,yy+28,YRAIL_Z,L-490,28,26,STEEL,"Y linear rail"),
        box(f"YRack_{side}",265,yy+70,590,L-530,18,18,BLACK,"Y rack gear")
    )
    for j in range(65):
        xx=285+j*49
        add(G_MOTION,box(f"RackTooth_{side}_{j:02d}",xx,yy+70,608,16,18,9,BLACK,"Rack tooth"))

for yy in (175,W-235):
    for k in (0,90):
        add(G_MOTION,box(f"YBlock_{int(yy)}_{k}",GANTRY_X-50+k,yy,YRAIL_Z+20,70,65,38,STEEL,"Y linear guide block"))

add(G_MOTION,
    chamfered_box("GantryMain",GANTRY_X,155,GANTRY_Z,GANTRY_W,W-310,GANTRY_H,18,BLUE_LIGHT,"Main gantry"),
    box("GantryTopCap",GANTRY_X+12,190,GANTRY_Z+GANTRY_H-10,GANTRY_W-24,W-380,38,BLUE,"Gantry top cap"),
    box("GantryEnd_L",GANTRY_X-92,140,GANTRY_Z-75,92,235,330,BLUE,"Gantry left end block"),
    box("GantryEnd_R",GANTRY_X-92,W-375,GANTRY_Z-75,92,235,330,BLUE,"Gantry right end block")
)

add(G_MOTION,
    box("XRailBar",GANTRY_X+42,315,GANTRY_Z+78,150,W-630,44,STEEL,"X axis rail bar"),
    box("Bellows_X_Left",GANTRY_X-43,220,GANTRY_Z+28,43,625,160,BLACK,"X bellows left"),
    box("Bellows_X_Right",GANTRY_X-43,W-845,GANTRY_Z+28,43,625,160,BLACK,"X bellows right")
)

# ==========================================================
# 04 CARRIAGE / Z / HEAD
# ==========================================================
CAR_Y=W/2-255

add(G_CARR,
    chamfered_box("MainCarriage",GANTRY_X-145,CAR_Y,525,410,510,690,22,BLUE,"Main moving carriage"),
    box("CarriageSide_L",GANTRY_X-132,CAR_Y+22,560,30,466,595,BLUE_LIGHT,"Carriage side left"),
    box("CarriageSide_R",GANTRY_X+235,CAR_Y+22,560,24,466,595,BLUE_LIGHT,"Carriage side right"),
    box("CarriageBlackInset",GANTRY_X+245,W/2-112,655,18,224,335,BLACK,"Branding inset"),
    box("CarriageBottomNose",GANTRY_X+18,W/2-95,510,95,190,155,BLUE_LIGHT,"Lower carriage nose"),
    box("ZLinearSlide",GANTRY_X+32,W/2-52,445,68,104,205,STEEL,"Z linear slide")
)

add(G_CARR,
    cz("LaserHeadTop",GANTRY_X+66,W/2,355,40,105,SILVER,"Laser head upper body"),
    cz("LaserHeadMid",GANTRY_X+66,W/2,285,32,75,STEEL,"Laser head middle"),
    cz("LaserHeadLower",GANTRY_X+66,W/2,225,23,65,DARKGRAY,"Laser head lower"),
    cz("LaserNozzle",GANTRY_X+66,W/2,180,10,48,RED,"Cutting nozzle")
)

for off,c in ((-18,YELLOW),(0,BLACK),(18,WHITE)):
    add(G_CARR,cy(f"HeadHose_{off}",GANTRY_X+85,W/2+off,610,8,200,c,"Head service hose"))

# ==========================================================
# 05 COVERS / PANELS
# ==========================================================
add(G_COV,
    chamfered_box("FrontBody",0,0,190,150,W,455,28,BLUE,"Front machine cover"),
    box("FrontTopMetal",0,110,645,760,W-220,34,STEEL,"Front top metal panel")
)

for yy in (205,420,635,850,1065,1280,1495,1710):
    for xx in (190,520):
        add(G_DETAIL,cz(f"TopBolt_{xx}_{yy}",xx,yy,674,14,18,SILVER,"Top cover bolt"))

add(G_COV,
    chamfered_box("SideCover_L",140,0,190,L-280,80,425,28,BLUE,"Left side cover"),
    chamfered_box("SideCover_R",140,W-80,190,L-280,80,425,28,BLUE,"Right side cover"),
    chamfered_box("RearCorner_L",L-190,0,190,130,185,425,42,BLUE,"Rear left corner"),
    chamfered_box("RearCorner_R",L-190,W-185,190,130,185,425,42,BLUE,"Rear right corner")
)

add(G_COV,
    box("ServiceOpeningUpper",L-205,W-155,315,65,80,150,BLACK,"Service opening upper"),
    box("ServiceOpeningLower",L-198,W-145,220,55,60,62,BLACK,"Service opening lower")
)

add(G_COV,
    box("EndBellows_L",270,85,610,430,135,190,BLACK,"Left front bellows"),
    box("EndBellows_R",270,W-220,610,430,135,190,BLACK,"Right front bellows")
)

add(G_DETAIL,
    box("GreenLED_L",18,125,310,10,22,260,GREEN,"Front indicator left"),
    box("GreenLED_R",18,W-147,310,10,22,260,GREEN,"Front indicator right")
)

for row in range(4):
    for col in range(5):
        y=CAR_Y+330+col*24
        z=780+row*24
        add(G_DETAIL,cy(f"Vent_{row}_{col}",GANTRY_X+257,y,z,6,10,BLACK,"Vent hole"))

# ==========================================================
# 06 CABLE CHAINS
# ==========================================================
for i in range(20):
    xx=820+i*68
    add(G_CHAIN,
        box(f"Chain_H_{i:02d}",xx,295,1040,58,120,42,BLACK,"Horizontal cable chain"),
        cz(f"ChainPin_H_{i:02d}",xx+29,300,1050,5,8,YELLOW,"Cable chain pin")
    )

loop = [
(2130,300,1085),(2170,300,1140),(2200,300,1205),(2220,300,1275),
(2220,300,1350),(2198,300,1420),(2160,300,1480),(2108,300,1520),
(2048,300,1538),(1988,300,1522),(1938,300,1482),(1900,300,1425),
(1878,300,1355),(1878,300,1280),(1893,300,1210),(1920,300,1150)
]
for i,(xx,yy,zz) in enumerate(loop):
    add(G_CHAIN,
        box(f"Chain_Loop_{i:02d}",xx,yy,zz,66,118,50,BLACK,"Vertical cable chain"),
        cz(f"ChainPin_V_{i:02d}",xx+33,yy+5,zz+10,5,8,YELLOW,"Cable chain pin")
    )

for i in range(15):
    add(G_CHAIN,box(f"Chain_Secondary_{i:02d}",1420+i*58,860,1048,50,98,32,BLACK,"Secondary cable chain"))

# ==========================================================
# 07 CONTROL CONSOLE
# ==========================================================
add(G_CTRL,
    box("CtrlBase",L-520,W+260,0,245,245,34,SILVER,"Control pedestal base"),
    box("CtrlPost",L-430,W+350,34,64,64,910,SILVER,"Control pedestal"),
    box("CtrlLowerJoint",L-455,W+332,115,115,100,90,SILVER,"Console lower joint"),
    box("CtrlScreenBack",L-535,W+282,940,260,70,420,SILVER,"Monitor housing"),
    box("CtrlScreen",L-548,W+270,955,286,18,438,BLACK,"Touch monitor"),
    cy("EStop",L-258,W+320,1125,22,38,RED,"Emergency stop")
)

# ==========================================================
# 08 EXTRA DETAILS
# ==========================================================
for idx,(yy,cc) in enumerate(((115,GREEN),(130,RED),(145,YELLOW),(160,BLACK))):
    add(G_DETAIL,cx(f"Wire_{idx}",255,yy,275,7,540,cc,"Visible cable bundle"))

add(G_DETAIL,
    box("JunctionBox",350,120,500,230,165,220,BLUE_DARK,"Electrical junction box"),
    box("JunctionFace",365,105,525,200,18,165,BLACK,"Junction face")
)

for i,yy in enumerate((150,210)):
    add(G_DETAIL,cy(f"Connector_{i}",455,yy,590,22,20,BLACK,"Connector opening"))

for k in range(6):
    add(G_DETAIL,cy(f"CarriageBolt_{k}",GANTRY_X-146,CAR_Y+65+k*65,830,7,10,SILVER,"Carriage bolt"))

add(G_DETAIL,
    box("BrandPlaque",8,W/2-300,360,12,600,150,BLUE_DARK,"Front branding plaque"),
    box("BrandRedMark",0,W/2-45,405,18,90,45,RED,"Brand red symbol")
)

doc.recompute()

if Gui:
    try:
        Gui.activeDocument().activeView().setCameraType("Perspective")
    except:
        pass
    Gui.activeDocument().activeView().viewAxonometric()
    Gui.activeDocument().activeView().fitAll()

try:
    out_path = App.getUserAppDataDir() + "SahandLaser_FiberCutter_FINAL.FCStd"
    doc.saveAs(out_path)
    print("FCStd saved to:", out_path)
except Exception as e:
    print("Automatic FCStd save skipped:", e)

print("==================================================")
print("SAHAND LASER FINAL VISUAL MODEL CREATED")
print("Overall approximate size: 4000 x 2000 x 700 mm")
print("Cutting area: 3000 x 1500 mm")
print("Use this as the master visual model for further STEP / web export work.")
print("==================================================")
